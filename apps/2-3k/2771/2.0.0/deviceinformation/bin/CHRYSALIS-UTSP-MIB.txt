CHRYSALIS-UTSP-MIB DEFINITIONS ::= BEGIN

--
-- SafeNet, Inc. MIB objects for the Luna SA device
--

IMPORTS
    MODULE-IDENTITY, NOTIFICATION-TYPE, OBJECT-TYPE, Counter32, enterprises FROM SNMPv2-SMI
    DisplayString FROM SNMPv2-TC;

chrysalis       OBJECT IDENTIFIER ::= { enterprises 12383 }
chrysalisSnmp   OBJECT IDENTIFIER ::= { chrysalis 3 }


chrysalisUtsp MODULE-IDENTITY
    LAST-UPDATED "201407171200Z"
    ORGANIZATION "www.safenet-inc.com"
    CONTACT-INFO    
     "postal: 20 Colonnade Road, Suite 200
                    Ottawa, ON
                    Canada
                    K2E 7M6

      phone:    1-613-723-5077
      email:    support@safenet-inc.com"
    DESCRIPTION
	 "SafeNet MIB objects for the Luna SA device"
    REVISION     "201407171200Z"
    DESCRIPTION
	 "Second release"
    ::= { chrysalisSnmp 1 }

--
-- top level structure
--
citsHsm       OBJECT IDENTIFIER ::= { chrysalisUtsp 1 }
citsNtls      OBJECT IDENTIFIER ::= { chrysalisUtsp 2 }
citsNtlsTraps OBJECT IDENTIFIER ::= { chrysalisUtsp 3 }

--
-- HSM scalars
--

hsmOperationRequests OBJECT-TYPE
    SYNTAX      Counter64
    MAX-ACCESS  read-only
    STATUS      current
    DESCRIPTION
	"This object indicates the total number of HSM operations requested."
    ::= { citsHsm 1 }

hsmOperationErrors OBJECT-TYPE
    SYNTAX      Counter64
    MAX-ACCESS  read-only
    STATUS      current
    DESCRIPTION
	"This object indicates the total number of HSM operations requested
    which have resulted in errors."
    ::= { citsHsm 2 }

hsmCriticalEvents OBJECT-TYPE
    SYNTAX      Counter64
    MAX-ACCESS  read-only
    STATUS      current
    DESCRIPTION
	"This object indicates the total number of critical HSM events detected."
    ::= { citsHsm 3 }

hsmNonCriticalEvents OBJECT-TYPE
    SYNTAX      Counter64
    MAX-ACCESS  read-only
    STATUS      current
    DESCRIPTION
	"This object indicates the total number of non-critical HSM events detected."
    ::= { citsHsm 4 }

--
-- NTLS scalars
--

ntlsOperStatus OBJECT-TYPE
    SYNTAX      INTEGER {
                up(1),        -- running
                down(2),      -- not running
                unknown(3)    -- status can not be determined for some reason
            }
    MAX-ACCESS  read-only
    STATUS      current
    DESCRIPTION
	"This object indicates the current operational state of the NTLS."
    ::= { citsNtls 1 }

ntlsConnectedClients OBJECT-TYPE
    SYNTAX     Gauge32
    MAX-ACCESS  read-only
    STATUS      current
    DESCRIPTION
        "This object indicates the current number of connected clients of the NTLS."
    ::= { citsNtls 2 }

ntlsLinks OBJECT-TYPE
    SYNTAX     Gauge32
    MAX-ACCESS  read-only
    STATUS      current
    DESCRIPTION
        "This object indicates the current number of links of the NTLS."
    ::= { citsNtls 3 }

ntlsSuccessfulClientConnections OBJECT-TYPE
    SYNTAX     Counter64
    MAX-ACCESS  read-only
    STATUS      current
    DESCRIPTION
        "This object indicates the total number of successful client connections of the NTLS."
    ::= { citsNtls 4 }

ntlsFailedClientConnections OBJECT-TYPE
    SYNTAX     Counter64
    MAX-ACCESS  read-only
    STATUS      current
    DESCRIPTION
        "This object indicates the total number of unsuccessful client connections of the NTLS."
    ::= { citsNtls 5 }

ntlsCertExpireDay OBJECT-TYPE
    SYNTAX     DisplayString (SIZE (0..128))
    MAX-ACCESS  read-only
    STATUS      current
    DESCRIPTION
        "This object indicates the expiry date of the NTLS server certificate."
    ::= { citsNtls 6 }


ntlsCertExpireNotify NOTIFICATION-TYPE
     OBJECTS { ntlsCertExpireDay  }
     STATUS current
     DESCRIPTION "Notify that the NTLS certificate will soon expire."
     ::= { citsNtlsTraps 1}


END
