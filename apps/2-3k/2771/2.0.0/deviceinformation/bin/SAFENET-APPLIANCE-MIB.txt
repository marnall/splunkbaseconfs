SAFENET-APPLIANCE-MIB DEFINITIONS ::= BEGIN

--
-- Copyright 2013-14 SafeNet, Inc. All rights reserved.
--
-- All rights reserved. This file contains information that is
-- proprietary to SafeNet, Inc. and may not be distributed
-- or copied without written consent from SafeNet, Inc.
--

IMPORTS
    MODULE-IDENTITY, NOTIFICATION-TYPE, OBJECT-TYPE, enterprises, 
       Counter64, Unsigned32, Gauge32  FROM SNMPv2-SMI
    DisplayString, TruthValue FROM SNMPv2-TC
    luna FROM SAFENET-GLOBAL-MIB;



appliance MODULE-IDENTITY
    LAST-UPDATED "201305060000Z"
    ORGANIZATION "www.safenet-inc.com"
    CONTACT-INFO    
     "postal: 20 Colonnade Road, Suite 200
                    Ottawa, ON
                    Canada
                    K2E 7M6

      phone:    1-613-723-5077
      email:    support@safenet-inc.com"
    DESCRIPTION
     "
           SafeNet MIB definition for Luna SA managed objects.

     "
    REVISION     "201401070000Z"
    DESCRIPTION  "Second release"
    ::= { luna 2 }

appSoftwareVersion OBJECT-TYPE
   SYNTAX      DisplayString
    MAX-ACCESS read-only
    STATUS     current
    DESCRIPTION
        "Appliance Software Version number."
    ::= { appliance 1 }  
	
ssTraps		OBJECT IDENTIFIER ::= { appliance 2 }
	
ssLogReference OBJECT-TYPE
    SYNTAX     DisplayString (SIZE (0..256))
    MAX-ACCESS  read-only
    STATUS      current
    DESCRIPTION
        "This object indicates the log record pertaining to the sub-system trap."
    ::= { ssTraps 1 }	
	
fanAttentionNotify NOTIFICATION-TYPE
     OBJECTS { ssLogReference  }
     STATUS current
     DESCRIPTION "Notify that a fan needs attention."
     ::= { ssTraps 2}

powerSupplyAttentionNotify NOTIFICATION-TYPE
     OBJECTS { ssLogReference  }
     STATUS current
     DESCRIPTION "Notify that a power supply needs attention."
     ::= { ssTraps 3}

motherboardAttentionNotify NOTIFICATION-TYPE
     OBJECTS { ssLogReference  }
     STATUS current
     DESCRIPTION "Notify that the motherboard needs attention."
     ::= { ssTraps 4}

diskDriveAttentionNotify NOTIFICATION-TYPE
     OBJECTS { ssLogReference  }
     STATUS current
     DESCRIPTION "Notify that a disk drive needs attention."
     ::= { ssTraps 5}
	 
ntlsAttentionNotify NOTIFICATION-TYPE
     OBJECTS { ssLogReference  }
     STATUS current
     DESCRIPTION "Notify that NTLS needs attention."
     ::= { ssTraps 6}

cryptoAttentionNotify NOTIFICATION-TYPE
     OBJECTS { ssLogReference  }
     STATUS current
     DESCRIPTION "Notify that the HSM needs attention."
     ::= { ssTraps 7}

clockAttentionNotify NOTIFICATION-TYPE
     OBJECTS { ssLogReference  }
     STATUS current
     DESCRIPTION "Notify that the system clock needs attention."
     ::= { ssTraps 8}
	 
END
