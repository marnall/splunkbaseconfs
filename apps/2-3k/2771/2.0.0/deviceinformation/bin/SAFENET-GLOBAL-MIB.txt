-- ******************************************************************************************************************
-- FILE:            SAFENET-GLOBAL-MIB.mib
--
-- CLASSIFICATION:
--
-- PROPERTY OF:     SafeNet
--
-- GENERATED AT:    SafeNet Inc.
--                  4690 Millennium Drive
--                  Belcamp, Maryland 21017
--
--                  Copyright (c) 2009 by SafeNet, Inc.
--                  All rights reserved.
--
-- DESCRIPTION:     SafeNet Global MIB definitions
--*******************************************************************************************************************

-- ******************************************************************************************************************                                                                                                                     
-- Safenet Global OID registration.
-- ******************************************************************************************************************
SAFENET-GLOBAL-MIB DEFINITIONS ::= BEGIN
                                                                                                                     
    -- **************************************************************************************************************                                                                                                                     
    -- IMPORTS
    -- **************************************************************************************************************
    IMPORTS
        MODULE-IDENTITY, enterprises
    FROM SNMPv2-SMI;

    -- **************************************************************************************************************                                                                                                                     
    -- MIB module identity
    -- **************************************************************************************************************
    mibSafenetGlobal MODULE-IDENTITY 

        LAST-UPDATED "201305221500Z"

        ORGANIZATION "SafeNet, Inc"

        CONTACT-INFO "
            4690 Millennium Drive
            Belcamp, MD 21017

            Technical Support:
                Phone: 1-800-545-6608 US Toll Free
                Phone: 1-410-931-7520 International
                E-mail: support@safenet-inc.com

            Government Technical Support:
                Phone: 1-866-307-7233
                E-mail: govsupport@safenet-inc.com"
              
        DESCRIPTION "SafeNet global OID registrations."
                
                    
        REVISION    "201305221500Z"
        DESCRIPTION "Added SafeNet Luna product sub tree."
        
        REVISION    "201206291430Z"
        DESCRIPTION "Added StorageSecure product, Technical Support info."

        REVISION    "200909090200Z"
        DESCRIPTION     "Set contact info to SafeNet Gov Support"
 
        REVISION    "200804031400Z"
        DESCRIPTION "Added revision section to MODULE-IDENTITY."

        ::= { safenetRoot 0 }

                       
    -- **************************************************************************************************************
    -- This is Safenet's IANA registered OID.  We branch the "safenetRoot" node from this node.
    -- **************************************************************************************************************
    safenet-inc OBJECT IDENTIFIER ::= { enterprises 23629 }
                       
    -- **************************************************************************************************************
    -- Node definitions
    -- **************************************************************************************************************

    -- The enterprise root for Safenet
    safenetRoot OBJECT IDENTIFIER ::= { safenet-inc 1 } 

        -- Safenet common section
        safenetCommon OBJECT IDENTIFIER ::= { safenetRoot 1 } 

            safenetCommonDevice OBJECT IDENTIFIER ::= { safenetCommon 1 }

            safenetCommonTc OBJECT IDENTIFIER ::= { safenetCommon 2 }

        -- Safenet high speed sub tree
        safenetHighSpeed OBJECT IDENTIFIER ::= { safenetRoot 2 }

            -- Safenet high speed common sub tree
            safenetHighSpeedCommon OBJECT IDENTIFIER ::= { safenetHighSpeed 1 }

                -- Safenet high speed common generic sub tree
                safenetHighSpeedCommonGeneric OBJECT IDENTIFIER ::= { safenetHighSpeedCommon 1 }

                -- Safenet high speed common type1 sub tree
                safenetHighSpeedCommonType1 OBJECT IDENTIFIER ::= { safenetHighSpeedCommon 2 }

                -- Safenet high speed common commercial sub tree
                safenetHighSpeedCommonCommercial OBJECT IDENTIFIER ::= { safenetHighSpeedCommon 3 }

            -- SafeNet high speed SONET
            safenetSonet OBJECT IDENTIFIER ::= { safenetHighSpeed 2 }

                -- Safenet SONET common
                safenetSonetCommon OBJECT IDENTIFIER ::= { safenetSonet 1 }

                -- Safenet SONET type1 device
                safenetSonetType1 OBJECT IDENTIFIER ::= { safenetSonet 2 }

                -- Safenet SONET commercial device
                safenetSonetCommercial OBJECT IDENTIFIER ::= { safenetSonet 3 }

            -- SafeNet high speed Ethernet 
            safenetEthernet OBJECT IDENTIFIER ::= { safenetHighSpeed 3 }

                -- Safenet ethernet encryption common
                safenetEthernetCommon OBJECT IDENTIFIER ::= { safenetEthernet 1 }

                -- Safenet ethernet type1 encryption device
                safenetEthernetType1 OBJECT IDENTIFIER ::= { safenetEthernet 2 }

                -- Safenet ethernet commercial encryption device
                safenetEthernetCommercial OBJECT IDENTIFIER ::= { safenetEthernet 3 }
  
        -- Safenet IMS sub tree
        safenetIMS OBJECT IDENTIFIER ::= { safenetRoot 3 }

            safenetIMSCommon OBJECT IDENTIFIER ::= { safenetIMS 1 }

            safenetBSF OBJECT IDENTIFIER ::= { safenetIMS 2 }

        -- StorageSecure sub tree
        storageSecure OBJECT IDENTIFIER ::= { safenetRoot 4 }
            
        -- Safenet Luna sub tree
        luna OBJECT IDENTIFIER ::= { safenetRoot 5 }
END

--
-- SAFENET-GLOBAL-MIB.mib
--
